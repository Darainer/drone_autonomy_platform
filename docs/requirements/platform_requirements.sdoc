[DOCUMENT]
TITLE: Drone Autonomy Platform Requirements
UID: DOC-PLATFORM-REQ
VERSION: 0.1

[TEXT]
STATEMENT: >>>
Canonical requirements for the drone autonomy platform in StrictDoc format.
Requirement IDs defined here (E2E-*, COMP-*, PLAT-*) are the single source of
truth — narrative documents such as docs/architecture/latency_requirements.md
reference these UIDs but do not define them.

Conventions are described in docs/requirements/README.md and the
`requirements` skill. Verify linkage with:
python scripts/check_traceability.py
<<<

[[SECTION]]
TITLE: End-to-End Latency (Surveying)

[TEXT]
STATEMENT: >>>
End-to-end latency is the time from a photon hitting the sensor to the drone
(or operator) acting on that information.
<<<

[REQUIREMENT]
UID: E2E-1
STATUS: Approved
TAGS: latency, surveying
TITLE: Sensor to GCS Display Latency
STATEMENT: >>>
The time from image capture on the sensor to display of that image on the
ground control station (GCS) shall not exceed 500 ms.
<<<
RATIONALE: >>>
Real-time situational awareness for the operator degrades rapidly beyond
half a second of display lag.
<<<

[REQUIREMENT]
UID: E2E-2
STATUS: Approved
TAGS: latency, surveying, safety-critical
TITLE: Sensor to Action Latency (Obstacle Avoidance)
STATEMENT: >>>
The time from detection of an obstacle in the flight path to initiation of an
avoidance action (e.g., an evasive maneuver) shall not exceed 250 ms.
<<<
RATIONALE: >>>
Safety-critical reaction bound: at the platform's typical 10 m/s survey
transit speed, 250 ms corresponds to 2.5 m traveled before the avoidance
action begins, preserving sufficient margin to alter the flight path around
static or moving obstacles.
<<<

[REQUIREMENT]
UID: E2E-3
STATUS: Approved
TAGS: latency, surveying
TITLE: Sensor to Action Latency (Feature Tracking)
STATEMENT: >>>
The time from detection of a tracked surface feature (e.g., a crop row or
survey line landmark) to a course adjustment that follows the feature shall
not exceed 300 ms.
<<<
RATIONALE: >>>
Required to maintain accurate survey lines / row following.
<<<

[[/SECTION]]

[[SECTION]]
TITLE: Component-Level Latency Budget

[REQUIREMENT]
UID: COMP-1
STATUS: Approved
TAGS: latency
TITLE: Camera Capture Latency
STATEMENT: >>>
The time from image capture to availability of the frame on the MIPI-CSI bus
shall not exceed 30 ms.
<<<
RELATIONS:
- TYPE: Parent
  VALUE: E2E-2

[REQUIREMENT]
UID: COMP-2
STATUS: Approved
TAGS: latency
TITLE: Image Processing Latency
STATEMENT: >>>
Image processing (debayering, color correction, resize) shall complete within
50 ms per frame.
<<<
RELATIONS:
- TYPE: Parent
  VALUE: E2E-2

[REQUIREMENT]
UID: COMP-3
STATUS: Approved
TAGS: latency, perception
TITLE: Object Detection Latency
STATEMENT: >>>
The object detection model shall produce detections within 100 ms of
receiving an input frame.
<<<
RATIONALE: >>>
Drives the RF-DETR pipeline design in
docs/architecture/perception_architecture.md.
<<<
RELATIONS:
- TYPE: Parent
  VALUE: E2E-2

[REQUIREMENT]
UID: COMP-4
STATUS: Approved
TAGS: latency, perception
TITLE: Object Tracking Latency
STATEMENT: >>>
Frame-to-frame object tracking shall complete within 50 ms per frame.
<<<
RELATIONS:
- TYPE: Parent
  VALUE: E2E-3

[REQUIREMENT]
UID: COMP-5
STATUS: Approved
TAGS: latency, autonomy
TITLE: Decision Making Latency
STATEMENT: >>>
The mission manager shall produce a decision within 20 ms of receiving
perception output.
<<<
RELATIONS:
- TYPE: Parent
  VALUE: E2E-2

[REQUIREMENT]
UID: COMP-6
STATUS: Approved
TAGS: latency, control, safety-critical
TITLE: Control Command Generation Latency
STATEMENT: >>>
A new control command (attitude/velocity setpoint) shall be generated within
10 ms of a decision being made.
<<<
RELATIONS:
- TYPE: Parent
  VALUE: E2E-2

[REQUIREMENT]
UID: COMP-7
STATUS: Approved
TAGS: latency, control, safety-critical
TITLE: Flight Controller Processing Latency
STATEMENT: >>>
The flight controller shall process a control command and output motor
commands within 10 ms.
<<<
RELATIONS:
- TYPE: Parent
  VALUE: E2E-2

[REQUIREMENT]
UID: COMP-8
STATUS: Approved
TAGS: latency, comms
TITLE: Data Link Uplink Latency
STATEMENT: >>>
Transmission of a command from the GCS to the drone shall not exceed 40 ms.
<<<

[REQUIREMENT]
UID: COMP-9
STATUS: Approved
TAGS: latency, comms
TITLE: Data Link Downlink Latency
STATEMENT: >>>
Transmission of the compressed video stream from the drone to the GCS shall
not exceed 100 ms.
<<<
RELATIONS:
- TYPE: Parent
  VALUE: E2E-1

[[/SECTION]]

[[SECTION]]
TITLE: Platform Processing

[REQUIREMENT]
UID: PLAT-1
STATUS: Approved
TAGS: latency, perception
TITLE: Sensor Input to Perception Output
STATEMENT: >>>
The mission computer shall complete perception processing (image processing,
detection, tracking) within 150 ms of sensor data availability.
<<<
RATIONALE: >>>
Sum of COMP-2, COMP-3, and COMP-4 budgets.
<<<
RELATIONS:
- TYPE: Parent
  VALUE: E2E-2

[REQUIREMENT]
UID: PLAT-2
STATUS: Approved
TAGS: latency, autonomy, control
TITLE: Perception Output to Control Command
STATEMENT: >>>
The mission computer shall generate a control command within 30 ms of
perception output being available.
<<<
RATIONALE: >>>
Sum of COMP-5 and COMP-6 budgets.
<<<
RELATIONS:
- TYPE: Parent
  VALUE: E2E-2

[REQUIREMENT]
UID: PLAT-3
STATUS: Approved
TAGS: latency
TITLE: Total Onboard Processing
STATEMENT: >>>
Total onboard processing from sensor data availability to control command
output shall not exceed 180 ms.
<<<
RATIONALE: >>>
Sum of PLAT-1 and PLAT-2 budgets.
<<<
RELATIONS:
- TYPE: Parent
  VALUE: E2E-2

[[/SECTION]]

[[SECTION]]
TITLE: Functional — Perception/Autonomy Data Flow

[REQUIREMENT]
UID: PER-1
STATUS: Draft
TAGS: perception, interface
TITLE: Fused Sensor Data Publication
STATEMENT: >>>
The perception node shall publish fused sensor data
(drone_autonomy_msgs/SensorData) on the canonical topic /sensor_data at the
camera frame rate.
<<<
RATIONALE: >>>
The perception node is the platform's sensor-fusion point (README software
architecture); downstream decision-making needs a single fused feed rather
than raw per-sensor topics.
<<<
RELATIONS:
- TYPE: Parent
  VALUE: PLAT-1

[REQUIREMENT]
UID: AUT-1
STATUS: Draft
TAGS: autonomy, interface
TITLE: Mission Decisions Use Fused Perception Output
STATEMENT: >>>
The autonomy node shall use the most recent fused sensor data received on
/sensor_data as the perceived-information input to every mission decision.
<<<
RATIONALE: >>>
COMP-5 budgets "a decision based on the perceived information", and PLAT-2
budgets perception output to control command — both presuppose that the
mission manager actually consumes perception output. Today autonomy_node has
no subscriptions and publishes missions blind.
<<<
RELATIONS:
- TYPE: Parent
  VALUE: PLAT-2

[[/SECTION]]

[[SECTION]]
TITLE: Functional — Survey Mapping (derived from STK-1)

[REQUIREMENT]
UID: MAP-1
STATUS: Draft
TAGS: navigation, mapping, safety-critical
TITLE: Survey Trajectory Generation
STATEMENT: >>>
The navigation subsystem shall generate a survey trajectory that covers an
operator-defined polygon with configurable forward and side image overlap.
<<<
RATIONALE: >>>
Photogrammetric reconstruction requires systematic coverage (typically >= 75%
forward / >= 60% side overlap); ad-hoc waypoint missions cannot guarantee it.
<<<
RELATIONS:
- TYPE: Parent
  VALUE: STK-1

[REQUIREMENT]
UID: MAP-2
STATUS: Draft
TAGS: mapping, interface
TITLE: Synchronized Survey Data Recording
STATEMENT: >>>
During a survey mission, the platform shall record camera frames together
with time-synchronized vehicle pose onboard.
<<<
RATIONALE: >>>
Georeferencing the reconstruction requires a pose prior per image;
synchronization error translates directly into map error.
<<<
RELATIONS:
- TYPE: Parent
  VALUE: STK-1

[REQUIREMENT]
UID: MAP-3
STATUS: Draft
TAGS: mapping, interface
TITLE: Survey Dataset Offload
STATEMENT: >>>
Recorded survey data shall be retrievable from the vehicle post-flight as a
single dataset in a documented format.
<<<
RELATIONS:
- TYPE: Parent
  VALUE: STK-1

[REQUIREMENT]
UID: MAP-4
STATUS: Draft
TAGS: mapping, offboard
TITLE: Post-Flight 3D Reconstruction
STATEMENT: >>>
The post-flight pipeline shall produce a georeferenced 3D reconstruction
(point cloud and textured mesh) from a recorded survey dataset without manual
intervention.
<<<
RELATIONS:
- TYPE: Parent
  VALUE: STK-1

[REQUIREMENT]
UID: MAP-5
STATUS: Draft
TAGS: mapping, validation
TITLE: Reconstruction Completeness
STATEMENT: >>>
The delivered reconstruction shall cover at least 95% of the operator-defined
survey polygon.
<<<
RATIONALE: >>>
Direct measure of STK-1 "complete 3D map"; validated per survey mission, not
per software unit.
<<<
RELATIONS:
- TYPE: Parent
  VALUE: STK-1

[REQUIREMENT]
UID: MAP-6
STATUS: Draft
TAGS: autonomy, mapping
TITLE: Survey Mission Type
STATEMENT: >>>
The mission manager shall accept a survey mission specification (polygon,
altitude, overlap parameters) and execute it as a mission of type "survey".
<<<
RATIONALE: >>>
Entry point of the capability: the operator tasks the platform at the level
of "survey this area", not individual waypoints.
<<<
RELATIONS:
- TYPE: Parent
  VALUE: STK-1

[REQUIREMENT]
UID: MAP-7
STATUS: Draft
TAGS: mapping, onboard
TITLE: Onboard Post-Flight Consistency Check
STATEMENT: >>>
The companion computer shall produce an onboard survey-dataset consistency
report (projected polygon coverage, frame/pose synchronization health, and
dataset completeness) within 15 minutes of survey mission completion.
<<<
RATIONALE: >>>
The Orin Nano class companion has sufficient processing power for post-flight
checks. An on-site consistency verdict lets the operator re-fly gaps before
leaving the survey area — directly supporting the STK-1 "complete" criterion
without a second mobilization.
<<<
RELATIONS:
- TYPE: Parent
  VALUE: STK-1

[REQUIREMENT]
UID: MAP-8
STATUS: Draft
TAGS: mapping, onboard
TITLE: Onboard Reconstruction Execution
STATEMENT: >>>
The post-flight reconstruction pipeline shall be executable on the companion
computer (Jetson Orin Nano class), producing the same map products as the
ground-station execution from the same dataset without manual intervention.
<<<
RATIONALE: >>>
One pipeline codebase, two execution targets: the ground station meets the
STK-1 2-hour product deadline; onboard execution removes the ground-station
dependency when time permits. Onboard runtime is documented, not bounded by
STK-1(c), which applies to the reference ground station.
<<<
RELATIONS:
- TYPE: Parent
  VALUE: STK-1

[[/SECTION]]

[[SECTION]]
TITLE: Functional — Pre-Mow Field Clearance (derived from STK-2)

[REQUIREMENT]
UID: CLR-1
STATUS: Draft
TAGS: autonomy, surveillance
TITLE: Clearance Mission Type
STATEMENT: >>>
The mission manager shall accept a clearance mission specification (a set of
named, operator-predefined area polygons, surveillance altitude, and a
mission profile — dawn thermal sweep or daytime visual final check) and
execute it as a mission of type "clearance", activating the profile's
detection modality and coverage parameters.
<<<
RATIONALE: >>>
Entry point of the capability: the farmer tasks the platform at the level of
"clear these fields before I mow", not individual waypoints. Area polygons
are defined once and reused per mowing cycle.
<<<
RELATIONS:
- TYPE: Parent
  VALUE: STK-2

[REQUIREMENT]
UID: CLR-2
STATUS: Draft
TAGS: perception, ml, surveillance
TITLE: Clearance Detection Performance
STATEMENT: >>>
During the daytime visual final check, the onboard perception subsystem shall
detect the clearance object classes (people, livestock, medium-and-larger
wild animals of at least fawn size ~0.4 m, vehicles, and agricultural
machinery) in RGB imagery at an effective ground sampling distance of
<= 4 cm/px at the detector input (operating point per DES-007), for objects
with vegetation occlusion up to grade O2 (<= 70%), achieving on the held-out
clearance evaluation set, binned by range and occlusion grade: person recall
>= 0.95, animal-class recall >= 0.85, at a false-finding rate <= 1 per
surveyed hectare.
<<<
RATIONALE: >>>
Misses are the costly failure mode (an undetected child or fawn defeats the
capability), so the requirement is stated as recall at a bounded
false-positive budget rather than mAP alone. "Effective GSD at detector
input" (not sensor-native GSD) is the binding quantity because the deployed
node resizes frames to the 512x512 engine input — see the DES-007 range
analysis. Fully concealed objects (grade O3) are out of RGB scope and
covered by the thermal dawn sweep (CLR-12). Numbers are Draft — confirmed
against the WP-A baseline evaluation before approval.
<<<
RELATIONS:
- TYPE: Parent
  VALUE: STK-2

[REQUIREMENT]
UID: CLR-3
STATUS: Draft
TAGS: perception, surveillance
TITLE: Persistent Object Tracking
STATEMENT: >>>
The perception subsystem shall associate per-frame detections into tracks
with persistent identifiers such that one physical object observed across
multiple frames yields exactly one finding, within the COMP-4 per-frame
tracking budget.
<<<
RATIONALE: >>>
Without tracking, a single cow generates hundreds of per-frame findings and
the report is unusable. Implements the ByteTrack integration already planned
in docs/architecture/perception_architecture.md.
<<<
RELATIONS:
- TYPE: Parent
  VALUE: STK-2

[REQUIREMENT]
UID: CLR-4
STATUS: Draft
TAGS: perception, surveillance
TITLE: Finding Geolocation
STATEMENT: >>>
Each finding shall be georeferenced to a WGS84 ground position with <= 5 m
horizontal error at the surveillance operating point, and classified as
inside or outside the mission's mow-area polygons.
<<<
RATIONALE: >>>
The farmer must be able to walk to the finding; 5 m places it within visual
range on open grassland. Projection uses camera intrinsics
(/oak/rgb/camera_info) plus time-synchronized vehicle pose, reusing the
synchronization approach proven in DES-004.
<<<
RELATIONS:
- TYPE: Parent
  VALUE: STK-2

[REQUIREMENT]
UID: CLR-5
STATUS: Draft
TAGS: surveillance, interface
TITLE: Evidence Clip Capture
STATEMENT: >>>
For every finding located inside a mow-area polygon, the platform shall
record onboard a video clip of at least 3 seconds (including at least 1
second before the first detection) together with a structured finding record
(class, confidence, track identifier, ground position, UTC time).
<<<
RATIONALE: >>>
The farmer investigates from the clip, not the raw stream — evidence must be
reviewable on a phone in seconds. Pre-roll requires a continuous rolling
frame buffer in the recorder.
<<<
RELATIONS:
- TYPE: Parent
  VALUE: STK-2

[REQUIREMENT]
UID: CLR-6
STATUS: Draft
TAGS: surveillance, onboard
TITLE: Clearance Report Generation
STATEMENT: >>>
Within 5 minutes of clearance mission completion, the companion computer
shall produce, without manual intervention, a clearance report containing:
a per-area verdict (CLEAR, or the number of findings), the finding records
with evidence clips, a map overlay of finding positions, and an explicit
statement of any mow-area regions not covered by surveillance imagery.
<<<
RATIONALE: >>>
The verdict must be trustworthy: an area is only CLEAR if it was actually
seen, so coverage holes are reported rather than silently ignored. Report
states the RGB surface-visibility limitation (STK-2 phase scope).
<<<
RELATIONS:
- TYPE: Parent
  VALUE: STK-2

[REQUIREMENT]
UID: CLR-7
STATUS: Draft
TAGS: comms, surveillance
TITLE: Mobile Report Delivery
STATEMENT: >>>
The clearance report shall be delivered to the operator's registered mobile
device over an available data link within 5 minutes of mission completion,
with a notification announcing per-area verdicts.
<<<
RATIONALE: >>>
The farmer is not at a ground station — delivery to the phone closes the
mission loop. Transport selection (LTE upload + push notification preferred,
local WiFi fallback) is a design decision recorded in the CAP-002 DES doc.
<<<
RELATIONS:
- TYPE: Parent
  VALUE: STK-2

[REQUIREMENT]
UID: CLR-8
STATUS: Draft
TAGS: navigation, surveillance, safety-critical
TITLE: Surveillance Coverage Trajectory
STATEMENT: >>>
The navigation subsystem shall generate a surveillance trajectory that covers
at least 95% of each mow-area polygon with imagery at the effective detection
ground sampling distance of the active mission profile (daytime RGB check:
<= 4 cm/px at detector input; dawn thermal sweep: <= 4.5 cm/px native), per
the DES-007 operating points.
<<<
RATIONALE: >>>
Reuses the MAP-1 coverage (lawnmower) generator with detection-driven,
per-profile parameterization (altitude/GSD/overlap for detection rather than
photogrammetric reconstruction). Residual uncovered area is reported per
CLR-6, never silently dropped.
<<<
RELATIONS:
- TYPE: Parent
  VALUE: STK-2

[REQUIREMENT]
UID: CLR-9
STATUS: Draft
TAGS: ml, offboard
TITLE: Training Data Provenance and Labeling Program
STATEMENT: >>>
Every dataset used to train or fine-tune the deployed clearance detection
model shall have a license compatible with commercial deployment, recorded in
a dataset provenance manifest; the domain fine-tuning set shall be produced
under a documented labeling plan meeting the annotation quality standards of
docs/architecture/perception_finetuning_plan.md.
<<<
RATIONALE: >>>
The fine-tuned model is a shipped product component: academic-only datasets
(VisDrone, DOTA class) may be used for prototyping but not in the deployed
training set (perception_finetuning_plan.md section 2.1.1). The labeling plan
is what makes the customer's domain (grassland, mow-height vegetation,
regional wildlife, farm machinery) actually represented in the data.
<<<
RELATIONS:
- TYPE: Parent
  VALUE: STK-2

[REQUIREMENT]
UID: CLR-10
STATUS: Draft
TAGS: autonomy, navigation, surveillance, safety-critical
TITLE: Finding Confirmation Maneuver
STATEMENT: >>>
For candidate findings below the confirmation confidence threshold, the
platform shall autonomously re-position over the finding location and
re-image it at close range (descend and native-resolution crop inference per
DES-007), confirming or dismissing the candidate; confirmations are bounded
by a configurable per-mission budget, and candidates left over budget are
reported as unconfirmed rather than dropped.
<<<
RATIONALE: >>>
v1 flies a single fixed camera, so "localize then zoom" is implemented by
craft movement: descending to ~10 m and running inference on a native-
resolution crop is a ~5x effective-GSD improvement over the survey pass
(DES-007 section 3.1). The maneuver is a normal waypoint insertion through
the existing trajectory/bridge path, but altitude-floor validation and abort
rules make the implementing packages safety-critical. A gimbal + optical
zoom system replacing this maneuver is recorded future extension FE-1.
<<<
RELATIONS:
- TYPE: Parent
  VALUE: STK-2

[REQUIREMENT]
UID: CLR-11
STATUS: Draft
TAGS: perception, hardware, surveillance
TITLE: Thermal Sensor Integration
STATEMENT: >>>
The platform shall integrate a LWIR thermal camera (640x512 class) as a ROS2
image source time-synchronized with vehicle pose, selectable as the active
detection modality for the dawn thermal sweep mission profile.
<<<
RATIONALE: >>>
Concealed animals (occlusion grade O3, e.g. a fawn bedded in tall grass) are
invisible to RGB at any resolution; dawn thermal contrast (overnight-cooled
ground vs. warm body) is the established detection mechanism (fawn-rescue
drone practice). Sensor candidates and selection criteria in DES-007
section 4.1; final sensor purchase requires owner sign-off.
<<<
RELATIONS:
- TYPE: Parent
  VALUE: STK-2

[REQUIREMENT]
UID: CLR-12
STATUS: Draft
TAGS: perception, ml, surveillance
TITLE: Concealed-Animal Thermal Detection
STATEMENT: >>>
During a dawn thermal sweep, the perception subsystem shall detect
warm-bodied animals of at least fawn size (~0.4 m) — including animals
partially or fully concealed in vegetation (occlusion grades O0-O3) —
achieving on the held-out thermal evaluation set, binned by range and
occlusion grade: animal recall >= 0.90 at a false-finding rate <= 1 per
surveyed hectare.
<<<
RATIONALE: >>>
The thermal sweep exists precisely for the O3 cases RGB cannot claim
(CLR-2). Detection approach is gated per DES-007 section 4.2: a classical
contrast/blob baseline is evaluated first; a fine-tuned model is built only
if the baseline fails the evaluation set. Residual risk under fully dense
canopy is stated in the clearance report.
<<<
RELATIONS:
- TYPE: Parent
  VALUE: STK-2

[[/SECTION]]

[[SECTION]]
TITLE: Safety

[REQUIREMENT]
UID: SAF-1
STATUS: Approved
TAGS: safety-critical, failsafe
TITLE: Critical Battery Return-to-Launch
STATEMENT: >>>
When the reported battery charge drops to 15% or below, the platform shall
command the flight controller into Return-to-Launch (RTL) mode exactly once
per discharge event.
<<<
RATIONALE: >>>
Prevents loss of airframe from battery exhaustion; single-shot trigger
avoids repeated mode-change spam that would fight operator overrides.
<<<

[REQUIREMENT]
UID: SAF-2
STATUS: Approved
TAGS: safety-critical, failsafe
TITLE: Low Battery Warning
STATEMENT: >>>
When the reported battery charge drops to 25% or below, the platform shall
emit a warning to the operator via telemetry and logs.
<<<

[[/SECTION]]
